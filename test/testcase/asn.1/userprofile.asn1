UserProfile-Module DEFINITIONS AUTOMATIC TAGS ::=
BEGIN

    -- 1. 사용자 정보를 담는 메인 구조체
    UserProfile ::= SEQUENCE {
        id          INTEGER (1..4294967295),       -- 1부터 시작하는 ID (범위 제한)
        username    IA5String (SIZE(3..20)),       -- 3~20자의 아이디
        isActive    BOOLEAN,                       -- 활성화 여부
        role        UserRole,                      -- 아래에 정의된 열거형 사용
        aliases     SEQUENCE OF IA5String OPTIONAL, -- 별명 목록 (있어도 되고 없어도 됨)
        contact     ContactInfo                    -- 연락처 정보 (CHOICE 타입)
    }

    -- 2. 열거형 정의
    UserRole ::= ENUMERATED {
        admin(0),
        user(1),
        guest(2)
    }

    -- 3. 초이스 타입 정의 (이메일 혹은 전화번호 중 하나만 선택)
    ContactInfo ::= CHOICE {
        email       IA5String,
        phoneNumber IA5String
    }

END
